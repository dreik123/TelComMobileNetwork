module mobile-network {
    namespace "ns:mobNetwork";

    prefix mobnet;

container core
{
   config true;

    list subscribers
    {
       key "number";

        leaf userName {
            config false;
            type string;
            description "User name ";
        }

        leaf number {
            description "User phone number";
            type string ;
        }
         
        leaf incomingNumber{
            description "Incoming number";
            type string;
        }

        leaf state{
            description "User's state";
            mandatory true;
            type enumeration {
                 enum busy; 
                 enum active ;
                 enum idle;
            }
        } 
        
    }
}
   
}
